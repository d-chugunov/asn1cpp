SOME-MODULE

DEFINITIONS IMPLICIT TAGS    ::=

BEGIN

SequenceRecord-PSSize-PSRefSize-PSRefCSize ::= SEQUENCE {
	str1 PrintableString (SIZE ((5..10) | (12..15))),
	str2 PSRefSize (SIZE (2..4)),
	str3 PSRefCSize
}

PSRefSize ::= PrintableString
PSRefCSize ::= PrintableString (SIZE (10..12))

END
