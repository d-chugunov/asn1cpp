SOME-MODULE

DEFINITIONS IMPLICIT TAGS    ::=

BEGIN

SequenceRecord-IA5-IA5Ref-IA5RefC ::= SEQUENCE {
	str1 IA5String (FROM ("a".."d") | ("f".."n")),
	str2 IA5Ref (FROM ("o".."r")),
	str3 IA5RefC
}

IA5Ref ::= IA5String
IA5RefC ::= IA5String (FROM ("s".."z"))

END
