SOME-MODULE

DEFINITIONS IMPLICIT TAGS    ::=

BEGIN

SequenceRecord-OSSize-OSRefSize-OSRefCSize ::= SEQUENCE {
	str1 OCTET STRING (SIZE ((5..10) | (12..15))),
	str2 OSRefSize (SIZE (2..4)),
	str3 OSRefCSize
}

OSRefSize ::= OCTET STRING
OSRefCSize ::= OCTET STRING (SIZE (10..12))

END
