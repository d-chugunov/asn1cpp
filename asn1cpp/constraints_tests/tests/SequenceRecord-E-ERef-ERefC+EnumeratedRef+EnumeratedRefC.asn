SOME-MODULE

DEFINITIONS IMPLICIT TAGS    ::=

BEGIN

SequenceRecord-E-ERef-ERefC ::= SEQUENCE {
	en1 ENUMERATED { val1(1), val2(50), val3(100) } (val1..val3),
	en2 EnumeratedRef (101..200),
	en3 EnumeratedRefC
}

EnumeratedRef ::= ENUMERATED
EnumeratedRefC ::= ENUMERATED (201..300)

END
