SOME-MODULE

DEFINITIONS IMPLICIT TAGS    ::=

BEGIN

SequenceRecord-PS-PSRef-PSRefC ::= SEQUENCE {
	str1 PrintableString (FROM ("a".."d") | ("f".."n")),
	str2 PSRef (FROM ("o".."r")),
	str3 PSRefC
}

PSRef ::= PrintableString
PSRefC ::= PrintableString (FROM ("s".."z"))

END
