SOME-MODULE

DEFINITIONS IMPLICIT TAGS    ::=

BEGIN

SequenceRecord-ODSize-ODRefSize-ODRefCSize ::= SEQUENCE {
	str1 ObjectDescriptor (SIZE ((5..10) | (12..15))),
	str2 ODRefSize (SIZE (2..4)),
	str3 ODRefCSize
}

ODRefSize ::= ObjectDescriptor
ODRefCSize ::= ObjectDescriptor (SIZE (10..12))

END
