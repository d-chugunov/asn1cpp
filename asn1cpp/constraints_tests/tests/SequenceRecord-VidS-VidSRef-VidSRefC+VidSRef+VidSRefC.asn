SOME-MODULE

DEFINITIONS IMPLICIT TAGS    ::=

BEGIN

SequenceRecord-VidS-VidSRef-VidSRefC ::= SEQUENCE {
	str1 VideotexString (FROM ("a".."d") | ("f".."n")),
	str2 VidSRef (FROM ("o".."r")),
	str3 VidSRefC
}

VidSRef ::= VideotexString
VidSRefC ::= VideotexString (FROM ("s".."z"))

END
