SOME-MODULE

DEFINITIONS IMPLICIT TAGS    ::=

BEGIN

SequenceRecord-VS-VSRef-VSRefC ::= SEQUENCE {
	str1 VisibleString (FROM ("a".."d") | ("f".."n")),
	str2 VSRef (FROM ("o".."r")),
	str3 VSRefC
}

VSRef ::= VisibleString
VSRefC ::= VisibleString (FROM ("s".."z"))

END
