SOME-MODULE

DEFINITIONS IMPLICIT TAGS    ::=

BEGIN

SequenceRecord-USSize-USRefSize-USRefCSize ::= SEQUENCE {
	str1 UniversalString (SIZE ((5..10) | (12..15))),
	str2 USRefSize (SIZE (2..4)),
	str3 USRefCSize
}

USRefSize ::= UniversalString
USRefCSize ::= UniversalString (SIZE (10..12))

END
