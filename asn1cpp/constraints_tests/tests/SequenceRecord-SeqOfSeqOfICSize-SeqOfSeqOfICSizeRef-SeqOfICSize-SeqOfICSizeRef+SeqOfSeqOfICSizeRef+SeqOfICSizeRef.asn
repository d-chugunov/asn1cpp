SOME-MODULE

DEFINITIONS IMPLICIT TAGS    ::=

BEGIN

SequenceRecord-SeqOfSeqOfICSize-SeqOfSeqOfICSizeRef-SeqOfICSize-SeqOfICSizeRef ::= SEQUENCE {
	seq1 SEQUENCE OF SEQUENCE (SIZE ((5..10) | (12..15))) OF INTEGER (10..20),
	seq2 SeqOfSeqOfICSizeRef,
	seq3 SEQUENCE (SIZE (20..30)) OF INTEGER (30..40),
	seq4 SeqOfICSizeRef
}

SeqOfSeqOfICSizeRef ::= SEQUENCE OF SEQUENCE (SIZE (2..3)) OF INTEGER (20..30)
SeqOfICSizeRef ::= SEQUENCE (SIZE (31..40)) OF INTEGER(40..50)

END
