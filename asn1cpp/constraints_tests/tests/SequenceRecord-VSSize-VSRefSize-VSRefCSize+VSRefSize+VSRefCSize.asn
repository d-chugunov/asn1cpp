SOME-MODULE

DEFINITIONS IMPLICIT TAGS    ::=

BEGIN

SequenceRecord-VSSize-VSRefSize-VSRefCSize ::= SEQUENCE {
	str1 VisibleString (SIZE ((5..10) | (12..15))),
	str2 VSRefSize (SIZE (2..4)),
	str3 VSRefCSize
}

VSRefSize ::= VisibleString
VSRefCSize ::= VisibleString (SIZE (10..12))

END
