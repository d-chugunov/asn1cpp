SOME-MODULE

DEFINITIONS IMPLICIT TAGS    ::=

BEGIN

SequenceRecord-I-IRefEq-IRefCEq ::= SEQUENCE {
	int1 INTEGER (100),
	int2 IntegerRefEq (200),
	int3 IntegerRefCEq
}

IntegerRefEq ::= INTEGER
IntegerRefCEq ::= INTEGER (300)

END
