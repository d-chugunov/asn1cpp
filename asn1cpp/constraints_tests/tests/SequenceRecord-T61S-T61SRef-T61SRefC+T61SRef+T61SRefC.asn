SOME-MODULE

DEFINITIONS IMPLICIT TAGS    ::=

BEGIN

SequenceRecord-T61S-T61SRef-T61SRefC ::= SEQUENCE {
	str1 T61String (FROM ("a".."d") | ("f".."n")),
	str2 T61SRef (FROM ("o".."r")),
	str3 T61SRefC
}

T61SRef ::= T61String
T61SRefC ::= T61String (FROM ("s".."z"))

END
