SOME-MODULE

DEFINITIONS IMPLICIT TAGS    ::=

BEGIN

SequenceRecord-UI-UIRef-UIRefC ::= SEQUENCE {
	int1 INTEGER (2147483648..2147483748),
	int2 UIntegerRef (2147483749..2147483848),
	int3 UIntegerRefC
}

UIntegerRef ::= INTEGER (2147483648..2147484000)
UIntegerRefC ::= INTEGER (2147483849..2147483948)

END
