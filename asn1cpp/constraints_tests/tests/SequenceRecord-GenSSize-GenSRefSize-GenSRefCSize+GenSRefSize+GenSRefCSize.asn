SOME-MODULE

DEFINITIONS IMPLICIT TAGS    ::=

BEGIN

SequenceRecord-GenSSize-GenSRefSize-GenSRefCSize ::= SEQUENCE {
	str1 GeneralString (SIZE ((5..10) | (12..15))),
	str2 GenSRefSize (SIZE (2..4)),
	str3 GenSRefCSize
}

GenSRefSize ::= GeneralString
GenSRefCSize ::= GeneralString (SIZE (10..12))

END
