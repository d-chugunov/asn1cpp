SOME-MODULE

DEFINITIONS IMPLICIT TAGS    ::=

BEGIN

SequenceRecord-I-IRef-IRefC ::= SEQUENCE {
	int1 INTEGER (1..100),
	int2 IntegerRef (101..200),
	int3 IntegerRefC
}

IntegerRef ::= INTEGER
IntegerRefC ::= INTEGER (201..300)

END
