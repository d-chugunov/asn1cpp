SOME-MODULE

DEFINITIONS IMPLICIT TAGS    ::=

BEGIN

SequenceRecord-TS-TSRef-TSRefC ::= SEQUENCE {
	str1 TeletexString (FROM ("a".."d") | ("f".."n")),
	str2 TSRef (FROM ("o".."r")),
	str3 TSRefC
}

TSRef ::= TeletexString
TSRefC ::= TeletexString (FROM ("s".."z"))

END
