SOME-MODULE

DEFINITIONS IMPLICIT TAGS    ::=

BEGIN

SequenceRecord-E-ERefEq-ERefCEq ::= SEQUENCE {
	en1 ENUMERATED { val1(1), val2(50), val3(100) } (val3),
	en2 EnumeratedRefEq (200),
	en3 EnumeratedRefCEq
}

EnumeratedRefEq ::= ENUMERATED
EnumeratedRefCEq ::= ENUMERATED (300)

END
