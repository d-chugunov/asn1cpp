SOME-MODULE

DEFINITIONS IMPLICIT TAGS    ::=

BEGIN

SequenceRecord-BSSize-BSRefSize-BSRefCSize ::= SEQUENCE {
	str1 BMPString (SIZE ((5..10) | (12..15))),
	str2 BSRefSize (SIZE (2..4)),
	str3 BSRefCSize
}

BSRefSize ::= BMPString
BSRefCSize ::= BMPString (SIZE (10..12))

END
