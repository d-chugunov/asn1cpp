SOME-MODULE

DEFINITIONS IMPLICIT TAGS    ::=

BEGIN

SequenceRecord-NSSize-NSRefSize-NSRefCSize ::= SEQUENCE {
	str1 NumericString (SIZE ((5..10) | (12..15))),
	str2 NSRefSize (SIZE (2..4)),
	str3 NSRefCSize
}

NSRefSize ::= NumericString
NSRefCSize ::= NumericString (SIZE (10..12))

END
