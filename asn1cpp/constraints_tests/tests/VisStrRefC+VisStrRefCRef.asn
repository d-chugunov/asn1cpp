ModuleTest1
	DEFINITIONS ::=
BEGIN
	IMPORTS VisStrRefC FROM ModuleTest2;

	VisStrRefCRef ::= VisStrRefC

END


ModuleTest2
	DEFINITIONS ::=
BEGIN
	EXPORTS VisStrRefC;

	maxLength INTEGER ::= 32

	VisStrRefC ::=
	    VisibleString ( FROM
	   ("A"|"a"|"B"|"b"|"C"|"c"|"D"|"d"|"E"|"e"|"F"|"f"|
	   "G"|"g"|"H"|"h"|"I"|"i"|"J"|"j"|"K"|"k"|"L"|"l"|
	   "M"|"m"|"N"|"n"|"O"|"o"|"P"|"p"|"Q"|"q"|"R"|"r"|
	   "S"|"s"|"T"|"t"|"U"|"u"|"V"|"v"|"W"|"w"|"X"|"x"|
	   "Y"|"y"|"Z"|"z"|"$"|"_"|"0"|"1"|"2"|"3"|"4"|"5"|
	   "6"|"7"|"8"|"9") ) (SIZE(1..maxLength))

END
