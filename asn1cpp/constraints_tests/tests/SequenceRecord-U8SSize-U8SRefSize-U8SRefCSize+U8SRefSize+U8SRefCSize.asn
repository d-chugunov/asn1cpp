SOME-MODULE

DEFINITIONS IMPLICIT TAGS    ::=

BEGIN

SequenceRecord-U8SSize-U8SRefSize-U8SRefCSize ::= SEQUENCE {
	str1 UTF8String (SIZE ((5..10) | (12..15))),
	str2 U8SRefSize (SIZE (2..4)),
	str3 U8SRefCSize
}

U8SRefSize ::= UTF8String
U8SRefCSize ::= UTF8String (SIZE (10..12))

END
