SOME-MODULE

DEFINITIONS IMPLICIT TAGS    ::=

BEGIN

SequenceRecord-ED-E-ED-ED ::= SEQUENCE {
	val1 [0] ENUMERATED DEFAULT 123,
	val2 [1] ENUMERATED,
	val3 [2] ENUMERATED DEFAULT 0,
	val4 [3] ENUMERATED DEFAULT 567
}

END
