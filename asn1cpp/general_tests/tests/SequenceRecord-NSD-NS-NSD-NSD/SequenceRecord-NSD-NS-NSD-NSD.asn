SOME-MODULE

DEFINITIONS IMPLICIT TAGS    ::=

BEGIN

SequenceRecord-NSD-NS-NSD-NSD ::= SEQUENCE {
	val1 [0] NumericString DEFAULT "12""3",
	val2 [1] NumericString,
	val3 [2] NumericString DEFAULT "567",
	val4 [3] NumericString DEFAULT "78*/9"
}

END
