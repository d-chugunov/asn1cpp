SOME-MODULE

DEFINITIONS IMPLICIT TAGS    ::=

BEGIN

SequenceRecord-ID-I-ID-ID ::= SEQUENCE {
	val1 [0] INTEGER DEFAULT 123,
	val2 [1] INTEGER,
	val3 [2] INTEGER DEFAULT 0,
	val4 [3] INTEGER DEFAULT 567
}

END
