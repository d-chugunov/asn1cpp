SOME-MODULE

DEFINITIONS IMPLICIT TAGS    ::=

BEGIN

SequenceRecord-IS-VisS-VisSO-VisSRefWithTag-VisSRefWithTagO ::= SEQUENCE {
	seq SEQUENCE {
		str1 VisibleString,
		str2 [1] VisibleString OPTIONAL,
		str3 VisibleStringRefWithTag,
		str4 VisibleStringRefWithTag OPTIONAL
	}
}

VisibleStringRefWithTag ::= [50] VisibleString

END
