SOME-MODULE

DEFINITIONS IMPLICIT TAGS    ::=

BEGIN

SetRecord-ThirdExtension ::= SET {
  a [0] INTEGER,
  ...,
  b [1] BOOLEAN,
  c [2] INTEGER,
  d [3] SET {
    e [0] INTEGER,
    ...,
    g [2] BOOLEAN OPTIONAL,
    h [3] BMPString,
    ...,
    f [1] IA5String
  }
}







END
