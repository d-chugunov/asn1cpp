SOME-MODULE

DEFINITIONS IMPLICIT TAGS    ::=

BEGIN

SequenceRecord-I646D-I646-I646D-I646D ::= SEQUENCE {
	val1 [0] ISO646String DEFAULT "12""3",
	val2 [1] ISO646String,
	val3 [2] ISO646String DEFAULT "567",
	val4 [3] ISO646String DEFAULT "78*/9"
}

END
