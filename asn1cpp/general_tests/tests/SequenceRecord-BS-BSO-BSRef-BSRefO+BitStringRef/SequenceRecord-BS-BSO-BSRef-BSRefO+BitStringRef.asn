SOME-MODULE

DEFINITIONS IMPLICIT TAGS    ::=

BEGIN

SequenceRecord-BS-BSO-BSRef-BSRefO ::= SEQUENCE {
	bitString1 BIT STRING,
	bitString2 [1] BIT STRING OPTIONAL,
	bitString3 BitStringRef,
	bitString4 BitStringRef OPTIONAL
}

BitStringRef ::= BIT STRING

END
