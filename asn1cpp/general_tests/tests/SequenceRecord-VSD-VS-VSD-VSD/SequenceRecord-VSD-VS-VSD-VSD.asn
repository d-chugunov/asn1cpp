SOME-MODULE

DEFINITIONS IMPLICIT TAGS    ::=

BEGIN

SequenceRecord-VSD-VS-VSD-VSD ::= SEQUENCE {
	val1 [0] VisibleString DEFAULT "12""3",
	val2 [1] VisibleString,
	val3 [2] VisibleString DEFAULT "567",
	val4 [3] VisibleString DEFAULT "78*/9"
}

END
