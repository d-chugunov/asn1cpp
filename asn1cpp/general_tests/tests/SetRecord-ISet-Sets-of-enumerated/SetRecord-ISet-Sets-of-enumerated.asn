SOME-MODULE

DEFINITIONS IMPLICIT TAGS    ::=

BEGIN

SetRecord-ISet-Sets-of-enumerated ::= SET {
	set SET {
		field3 [3]  SET OF ENUMERATED
                        {
                            value1           (1),
                            value2           (2),
                            value3          (3)
                        },
		field4 [4]  SET OF ENUMERATED
                        {
                            value1           (1),
                            value2           (2),
                            value3          (3)
                        } OPTIONAL
	}
}


END
