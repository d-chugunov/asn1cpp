SOME-MODULE

DEFINITIONS IMPLICIT TAGS    ::=

BEGIN

SequenceRecord-DirectRef ::= SEQUENCE {
	field DirectRefRecord-S-I-IO-I
}

DirectRefRecord-S-I-IO-I ::= SequenceRecord-I-IO-I

SequenceRecord-I-IO-I    ::= SEQUENCE {
	type [10] INTEGER,
	type2 [11] INTEGER OPTIONAL,
	type3 [12] INTEGER
}
 

END
