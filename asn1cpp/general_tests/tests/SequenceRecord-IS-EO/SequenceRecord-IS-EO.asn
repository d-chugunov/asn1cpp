SOME-MODULE

DEFINITIONS IMPLICIT TAGS    ::=

BEGIN

SequenceRecord-IS-EO ::= SEQUENCE {

        field SEQUENCE {
                value ENUMERATED
                        {
                            value1           (0),
                            value2           (1),
                            value3          (2)
                        } OPTIONAL
        }
}

END
