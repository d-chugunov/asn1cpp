SOME-MODULE

DEFINITIONS IMPLICIT TAGS    ::=

BEGIN

SetRecord-SecondExtension ::= SET {
  a [0]INTEGER,
  ...,
  b [1] BOOLEAN,
  c [2] INTEGER,
  d [3] SET {
    e [0] INTEGER,
    ...,
    ...,
    f [1] IA5String
  }
}







END
