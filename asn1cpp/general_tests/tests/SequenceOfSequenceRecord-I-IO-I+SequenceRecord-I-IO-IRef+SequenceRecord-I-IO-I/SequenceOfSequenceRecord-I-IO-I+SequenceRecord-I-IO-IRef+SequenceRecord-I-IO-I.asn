SOME-MODULE

DEFINITIONS IMPLICIT TAGS    ::=

BEGIN

SequenceOfSequenceRecord-I-IO-I ::= SEQUENCE OF SequenceRecord-I-IO-IRef

SequenceRecord-I-IO-IRef ::= SequenceRecord-I-IO-I

SequenceRecord-I-IO-I    ::= SEQUENCE {
        type [10] INTEGER,
        type2 [11] INTEGER OPTIONAL,
        type3 [12] INTEGER
}


END
