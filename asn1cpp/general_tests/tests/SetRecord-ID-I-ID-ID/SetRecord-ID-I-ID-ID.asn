SOME-MODULE

DEFINITIONS IMPLICIT TAGS    ::=

BEGIN

SetRecord-ID-I-ID-ID ::= SET {
	val1 [0] INTEGER DEFAULT 123,
	val2 [1] INTEGER,
	val3 [2] INTEGER DEFAULT 0,
	val4 [3] INTEGER DEFAULT 567
}

END
